;---------
(DEFUN acttodos ()
  (foreach x '(actmarca actglobal actfija actcero acttipo actfi actnumero actangulo actposic actreflejo acta actb actc actg actd acte actf actr)
    (set x "1")
  )                                 
  (foreach x '("actmarca" "actglobal" "actfija" "actcero" "acttipo" "actfi" "actnumero" "actangulo" "actposic" "actreflejo" "acta" "actb" "actc" "actg" "actd" "acte" "actf" "actr")
    (set_tile x (eval (read x)))
  )                                 
)
;---------
(DEFUN actninguno ()
  (foreach x '(actmarca actglobal actfija actcero acttipo actfi actnumero actangulo actposic actreflejo acta actb actc actg actd acte actf actr)
    (set x "0")
  )                                 
  (foreach x '("actmarca" "actglobal" "actfija" "actcero" "acttipo" "actfi" "actnumero" "actangulo" "actposic" "actreflejo" "acta" "actb" "actc" "actg" "actd" "acte" "actf" "actr")
    (set_tile x (eval (read x)))
  )                                 
)
;---------
(DEFUN C:ACTUALIZARM ()
  (GRABAR_RESPALDO)
  (setq Rcero cero Rangulo angulo)
  (CARGAR "C:llamarTX"   "datext")   
  
  (setvar "cmdecho" 0)
  (setvar "blipmode" 0)
  
  (foreach x '(actmarca actglobal actfija actcero acttipo actfi actnumero actangulo actposic actreflejo acta actb actc actg actd acte actf actr)
    (if (= (eval x) nil)(set x "0"))
  )                                 
  
  (setq opcionACTM 0)
  (SETQ DCL2 (LOAD_DIALOG "varios.dcl"))
  (SETQ CAJAB3 (NEW_DIALOG "actualizarm" DCL2))
  
  (foreach x '("actmarca" "actglobal" "actfija" "actcero" "acttipo" "actfi" "actnumero" "actangulo" "actposic" "actreflejo" "acta" "actb" "actc" "actg" "actd" "acte" "actf" "actr")
    (set_tile x (eval (read x)))
    (action_tile x "(set (read $key) (atoa $value)) ")
  )                                 
    
  (set_tile "incmar" incmar)
  (if (= oppremar 1)
    (set_tile "vism" "Se Visualizaran Codigos")
    (set_tile "vism" "Se Visualizaran Marcas")
  )
  (action_tile "incmar" "(setq incmar (itoa (atoi $value)))(set_tile \"incmar\" incmar)")
  
  (set_tile "acttmarca" Mmarca)
  (set_tile "acttglobal" Mglobal)
  (if (= Mfija "1")(set_tile "acttfija" "Si")(set_tile "acttfija" "No"))
  (if (= cero 1)(set_tile "acttcero" "No")(set_tile "acttcero" "Si"))
  
  (set_tile "actttipo" Mtipo)
  (set_tile "acttfi" fi)
  (set_tile "acttnumero" numero)
  
  (set_tile "acttangulo" angulo)
  (if (= posic 1)(set_tile "acttposic" "Izq"))
  (if (= posic 2)(set_tile "acttposic" "Cen"))
  (if (= posic 3)(set_tile "acttposic" "Der"))
  (if (= reflejo 1)(set_tile "acttreflejo" "Nor"))
  (if (= reflejo 2)(set_tile "acttreflejo" "X"))
  (if (= reflejo 3)(set_tile "acttreflejo" "X-Y"))
  (if (= reflejo 4)(set_tile "acttreflejo" "Y"))
  
  (set_tile "actta" aaa)
  (set_tile "acttb" bbb)
  (set_tile "acttc" ccc)
  (set_tile "acttd" ddd)
  (set_tile "actte" eee)
  (set_tile "acttf" fff)
  (set_tile "acttg" ggg)
  (set_tile "acttr" rrr)
  
  (action_tile "acttodos"   "(acttodos)")
  (action_tile "actninguno" "(actninguno)")
  
  (action_tile "actm" "(setq opcionACTM 1)(done_dialog)")
  
  (START_DIALOG)
  (DONE_DIALOG)
  (UNLOAD_DIALOG DCL2)
  
  (cond
    ((= opcionACTM 1)
      (setq MMfija Mfija actfijaa actfija)
      (if (= actmarca "1")(setq MMfija "1" actfija "1"))
      (if (and (= actglobal "1")(= actmarca "0"))(setq MMfija "0" actfija "1"))
      (ACTUAL 0)
      (LLAMAR_RESPALDO)
      (setq cero Rcero angulo Rangulo actfija actfijaa)
      (C:ACTUALIZARM)
    )
  )

  (setvar "cmdecho" old2)
  (setvar "blipmode" blipmodeANT)
  (LLAMAR_RESPALDO)
  (setq cero Rcero angulo Rangulo)
)

;---------
(DEFUN ACTUAL (acpipo)
  (setvar "cmdecho" 0)
  (setvar "blipmode" 0)
  (setq s1 (ssget '((0 . "text,polyline") (-3 ("acerTX,acerPL")))))
  (if (= s1 nil)
    (alert "   No se ha seleccionado ni Marcas ni Aceros  ")
    (progn
      (setq ls1 (sslength s1))
      (setq contar 0)
      (repeat ls1
        (LLAMAR_RESPALDO)
        (setq e1 (ssname s1 contar))
        (setq propie1 (entget e1))
        (if (/= propie1 nil)
          (progn
            (setq tipoe1 (cdr (assoc 0 propie1)))
            (if (= tipoe1 "TEXT")
              (ACTUALTEXT)
              (ACTUALPOLY)
            )
          )
        )
        (setq contar (1+ contar))
      )
    )
  )
)

;---------
(DEFUN ACTUALTEXT ()
  (c:llamarTX e1)
  (setq epl (handent WHPL)) 
  (if (= epl nil)
    (ACTGRATEXT e1 nil)
    (if (= (entget epl) nil)
      (ACTGRATEXT e1 nil)
      (ACTGRATEXTPOLY e1 epl)
    )
  )
)

;---------
(DEFUN ACTUALPOLY ()
  (c:llamarPL e1)
  (setq etx (handent WHNT)) 
  (if (= etx nil)
    (ACTGRAPOLY nil e1)
    (if (= (entget etx) nil)
      (ACTGRAPOLY nil e1)
      (ACTGRATEXTPOLY etx e1)
    )
  )
)
;==========333333333
;---------
(DEFUN ACTGRATEXTPOLY (eettxx eeppll)
  (setvar "cmdecho" 0)(setvar "blipmode" 0)
  (if (= acpipo 1)
    (progn (c:llamarTX eettxx)(c:llamarPL eeppll))
    (progn (c:llamarPL eeppll)(c:llamarTX eettxx))
  )   
  (setq accp 0)
  
  (if (or (= actmarca "1")(= actglobal "1")(= actfija "1")(= actcero "1")(= actfi "1")(= actnumero "1"))
    (if (and (= acttipo "0")(= actangulo "0")(= actposic "0")(= actreflejo "0")(= acta "0")(= actb "0")(= actc "0")(= actd "0")(= acte "0")(= actf "0")(= actg "0")(= actr "0"))
      (progn 
        (c:llamarTX eettxx)(c:llamarPL eeppll)
        (setq accp 1)
        (setq pipin (cdr (assoc 11 (entget eettxx))))
      )
    )
  )   
  
  (DATOTEXT)(OBTPUNTOPOLY eettxx eeppll) 
  (OBTANGULOPOLY)   
  (command "_erase" eeppll "")
  (if (= acpipo 0)(LLAMAR_RESPALDO_ACT))
     
  (MTIPOFI)(GRAPOLY_ACT)
  
  (setq lista1 (ARMAR ent))
  
  (if (= accp 1)
    (progn
      (c:llamarTX eettxx)
      (DATOTEXT)
      (if (= acpipo 0)(LLAMAR_RESPALDO_ACT))
    )
  )
  (command "_erase" eettxx "")
  
  (GRATEXT_ACT)

  (setq propient  (entget ent))
  (setq propientt (entget entt))
  (setq HPL (cdr (assoc 5 propient)))
  (setq HNT (cdr (assoc 5 propientt)))
  (setq HTX WHTX)
     
  (setq codigoANT codigo)
  (if (and (= cero 0)(= actcero "1"))(setq codigo "0"))
  (c:grabarTX entt)
  (c:grabarPL ent)
  (setq codigo codigoANT)
  (setq accp 0)
     
  (CONDIANT)
)
;---------
(DEFUN ACTGRATEXT (eettxx eeppll)
  (setvar "cmdecho" 0)(setvar "blipmode" 0)
  (c:llamarTX eettxx)
      
  (setq accp 0)
  
  (DATOTEXT)(setq punto (cdr (assoc 11 (entget eettxx))))
  (OBTANGULOTEXT)   
     
  (command "_erase" eettxx "")
  (LLAMAR_RESPALDO_ACT)
     
  (MTIPOFI)
     
  (setq lista1 "no")
  (GRATEXT_ACT)

  (setq HTX WHTX)
  (setq HPL "no")
  (setq HNT "no")
     
  (setq codigoANT codigo)
  (if (= cero 0)(setq codigo "0"))
  (c:grabarTX entt)
  (setq codigo codigoANT)
     
  (CONDIANT)
)
;---------
(DEFUN ACTGRAPOLY (eettxx eeppll)
  (setvar "cmdecho" 0)(setvar "blipmode" 0)
  (c:llamarPL eeppll)
      
  (setq accp 0)
  
  (DATOPOLY)(OBTPUNTOPOLY eettxx eeppll)
  (OBTANGULOPOLY)   
     
  (command "_erase" eeppll "")
  (LLAMAR_RESPALDO_ACT)
     
  (MTIPOFI)(GRAPOLY_ACT)
     
  (setq HNT "no")
  (c:grabarPL ent)
     
  (CONDIANT)
)
;==========333333333
;---------
(DEFUN PRENDIDO (encen)
  (if (= encen 1)(setq repet 11)(setq repet 11))
  (repeat repet
    (setq cont 0)
    (repeat esp
      (setq cont (1+ cont))
      (setq x1 (+ 0 margen cont) x2 (- pzxx margen cont)) 
      (setq y1 (+ 0 margen cont) y2 (- pzyy margen cont)) 
      (cond
        ((= encen 1)
          (start_image "enlazar")
            (vector_image  x1   y1   x2   y1   7)
            (vector_image  x2   y1   x2   y2   0)
            (vector_image  x2   y2   x1   y2   0)
            (vector_image  x1   y2   x1   y1   7)
          (end_image)
        )
        ((= encen 2)
          (start_image "enlazar")
            (vector_image  x1   y1   x2   y1   0)
            (vector_image  x2   y1   x2   y2   7)
            (vector_image  x2   y2   x1   y2   7)
            (vector_image  x1   y2   x1   y1   0)
          (end_image)
        )
      )
    )
  )

)

;---------
(DEFUN C:ENLAZAR ()
  (setq esp 5 margen 1)
  
  (GRABAR_RESPALDO)
  (CARGAR "C:llamarTX" "datext")   
  (CARGAR "C:EJECUTAR" "layer-1")
  
  (setvar "cmdecho" 0)
  (setvar "blipmode" 0)
  
  (setq opcionENLAZAR 0)
  (SETQ DCL2 (LOAD_DIALOG "varios.dcl"))
  (SETQ CAJAB3 (NEW_DIALOG "graficos" DCL2))
  
  (TIPOGRA2 "enlace" "enlace" "enlace-I" 0)
  (TIPOGRA2 "enlaces" "enlaces" "enlazar" 253)
  
  (setq pzxx (1- (dimx_tile "enlazar")))
  (setq pzyy (1- (dimy_tile "enlazar")))
  (PRENDIDO 1)
  
  (SET_TILE "tlayerdib" layerdib)
  (LAY layerdib "imagenDIB")
  (action_tile "layerdib" "(setq layerdib (C:EJECUTAR layerdib)) (LAY layerdib \"imagenDIB\") (SET_TILE \"tlayerdib\" layerdib) ")
  
  (DARREGLO)
  (EARREGLO)

  (action_tile "verenla"   "(setq enlac 1)(EARREGLO)")
  (action_tile "enla"      "(setq enlac 2)(EARREGLO)")
  (action_tile "desenla"   "(setq enlac 3)(EARREGLO)")
  (action_tile "mirarenla" "(setq enlac 4)(EARREGLO)")
  
  (action_tile "Dbloques"  "(setq dibuj 1)(DARREGLO)")
  (action_tile "Dmarcas"   "(setq dibuj 2)(DARREGLO)")
  (action_tile "Dvigas"    "(setq dibuj 3)(DARREGLO)")
  (action_tile "Destribos" "(setq dibuj 4)(DARREGLO)")
  (action_tile "Dgradas"   "(setq dibuj 5)(DARREGLO)")
  (action_tile "Dvarios"   "(setq dibuj 6)(DARREGLO)")
  (action_tile "Dlosa"     "(setq dibuj 7)(DARREGLO)")
  (action_tile "Dcorte"    "(setq dibuj 8)(DARREGLO)")
  
  (action_tile "enlazar"    "(PRENDIDO 2)(setq opcionENLAZAR 1)(PRENDIDO 1)(done_dialog)")
  (action_tile "dibujar"    "(setq opcionENLAZAR 2)(done_dialog)")
  (ACTION_TILE "undog"      "(setq opcionENLAZAR 3)(done_dialog)")
  (action_tile "imagenDIB"  "(setq opcionENLAZAR 4)(done_dialog)")
  
  (START_DIALOG)
  (DONE_DIALOG)
  (UNLOAD_DIALOG DCL2)
  
  (cond
    ((= opcionENLAZAR 4)
     (FUNKACOLOR layerdib)
     (C:ENLAZAR)
    )
    ((= opcionENLAZAR 3)
     (C:PANZOON1)
     (C:ENLAZAR)
    )
    ((and (= opcionENLAZAR 2)(= dibuj 1))
      (CARGAR "C:DIBBLOQUES" "graficos")(C:DIBBLOQUES)(LLAMAR_RESPALDO)
      (C:ENLAZAR)
    )
    ((and (= opcionENLAZAR 2)(= dibuj 2))
      (CARGAR "C:DIBMARCAS" "graficos")(C:DIBMARCAS)(LLAMAR_RESPALDO)
      (C:ENLAZAR)
    )
    ((and (= opcionENLAZAR 2)(= dibuj 3))
      (CARGAR "C:DIBVIGAS" "graficos")(C:DIBVIGAS)(LLAMAR_RESPALDO)
      (C:ENLAZAR)
    )
    ((and (= opcionENLAZAR 2)(= dibuj 4))
      (CARGAR "C:DIBESTRIBOS" "graficos")(C:DIBESTRIBOS)(LLAMAR_RESPALDO)
      (C:ENLAZAR)
    )
    ((and (= opcionENLAZAR 2)(= dibuj 5))
      (CARGAR "C:DIBGRADAS" "graficos")(C:DIBGRADAS)(LLAMAR_RESPALDO)
      (C:ENLAZAR)
    )
    ((and (= opcionENLAZAR 2)(= dibuj 6))
      (CARGAR "C:DIBVARIOS" "graficos")(C:DIBVARIOS)(LLAMAR_RESPALDO)
      (C:ENLAZAR)
    )
    ((and (= opcionENLAZAR 2)(= dibuj 7))
      (CARGAR "C:DIBLOSA" "graficos")(C:DIBLOSA)(LLAMAR_RESPALDO)
      (C:ENLAZAR)
    )
    ((and (= opcionENLAZAR 2)(= dibuj 8))
      (CARGAR "C:DIBCORTE" "graficos")(C:DIBCORTE)(LLAMAR_RESPALDO)
      (C:ENLAZAR)
    )
    ((and (= opcionENLAZAR 1)(= enlac 1))
      (VERENLA)
      (LLAMAR_RESPALDO)
      (C:ENLAZAR)
    )
    ((and (= opcionENLAZAR 1)(= enlac 2))
      (setq ee (entsel"\nPicar Texto Marca o Acero : "))
      (while (/= ee nil)
        (SUPERENLACE)
        (if (or (= etx nil)(= epl nil))
          (alert "   Seleccion de Texto Marca y Acero incorrecta   ")
          (ENLA)
        )
        (if (/= etx nil)(redraw etx 3))
        (if (/= epl nil)(redraw epl 3))
        (setq ee (entsel"\nPicar Texto Marca o Acero : "))
        (if (/= etx nil)(redraw etx 4))
        (if (/= epl nil)(redraw epl 4))
      )
      (LLAMAR_RESPALDO)
      (C:ENLAZAR)
    )
    ((and (= opcionENLAZAR 1)(= enlac 3))
      (setq ee (entsel"\nPicar Texto Marca o Acero : "))
      (while (/= ee nil)
        (DESENLACE)
        (if (and (= etx nil)(= epl nil))
          (alert "   Seleccion de Texto Marca y Acero incorrecta   ")
          (DESENLA)
        )
        (if (/= etx nil)(redraw etx 3))
        (if (/= epl nil)(redraw epl 3))
        (setq ee (entsel"\nPicar Texto Marca o Acero : "))
        (if (/= etx nil)(redraw etx 4))
        (if (/= epl nil)(redraw epl 4))
      )
      (LLAMAR_RESPALDO)
      (C:ENLAZAR)
    )
    ((and (= opcionENLAZAR 1)(= enlac 4))
      (setq ee (car (entsel "\nPique Texto Marca o Acero : ")))
      (while (/= ee nil)
        (MIRARENLACE)
        (if (/= etx nil)(redraw etx 3))
        (if (/= epl nil)(redraw epl 3))
        (setq ee (car (entsel "\nPique Texto Marca o Acero : ")))
        (if (/= etx nil)(redraw etx 4))
        (if (/= epl nil)(redraw epl 4))
      )
      (LLAMAR_RESPALDO)
      (C:ENLAZAR)
    )
  )

  (setvar "cmdecho" old2)
  (setvar "blipmode" blipmodeANT)
  (LLAMAR_RESPALDO)
)

;---------
(DEFUN SUPERENLACE ()
  (setq etx nil epl nil)
  (if (= ee nil)
    (alert "   No se ha picado Nada   ")
    (progn
      (if (= (type ee) (read "LIST"))(setq ee (car ee)))
      (setq tipoee (cdr (assoc 0 (entget ee))))
          
      (cond
        ((= tipoee "TEXT")
          (setq etx ee)(redraw etx 3)
          (setq ee (entsel"\nPicar Acero : "))
          (if (= ee nil)
            (alert "   No se ha picado Nada   ")
            (progn
              (setq ee (car ee))
              (setq tipoeee (cdr (assoc 0 (entget ee))))
              (if (= tipoeee "POLYLINE")
                (progn (setq epl ee)(redraw epl 3))
              )
            )
          )
        )
        ((= tipoee "POLYLINE")
          (setq epl ee)(redraw epl 3)
          (setq ee (entsel"\nPicar Texto Marca : "))
          (if (= ee nil)
            (alert "   No se ha picado Nada   ")
            (progn
              (setq ee (car ee))
              (setq tipoeee (cdr (assoc 0 (entget ee))))
              (if (= tipoeee "TEXT")
                (progn (setq etx ee)(redraw etx 3))
              )
            )
          )
        )
      )
    )  
  )

)

;---------
(DEFUN DESENLACE ()
  (setq etx nil epl nil)
  (if (= ee nil)
    (alert "   No se ha picado Nada   ")
    (progn
      (if (= (type ee) (read "LIST"))(setq ee (car ee)))
      (setq tipoee (cdr (assoc 0 (entget ee))))
      (cond
        ((= tipoee "TEXT")
          (c:llamarTX ee)
          (if (/= tieneV nil)
            (progn
              (setq etx ee)(setq epl (handent WHPL))
            )
          )
        )
        ((= tipoee "POLYLINE")
          (c:llamarPL ee)
          (if (/= tieneP nil)
            (progn
              (setq epl ee)(setq etx (handent WHNT))
            )
          )
        )
      )
    )  
  )

)

;---------
(DEFUN MIRARENLACE ()
  (setq etx nil epl nil)
  (if (= ee nil)
    (alert "   No se ha picado Nada   ")
    (progn
      (setq tipoee (cdr (assoc 0 (entget ee))))
      (cond
        ((= tipoee "TEXT")
          (setq etx ee)(c:llamarTX etx)(setq HPL WHPL)
          (redraw etx 3)
          (setq ee (handent HPL))
          (if (or (= ee nil)(= tieneV nil))
            (alert "   Texto Marca sin Enlace   ")
            (if (= (entget ee) nil)
              (alert "   Texto Marca sin Enlace   ")
              (setq epl ee)
            )
          )
        )
        ((= tipoee "POLYLINE")
          (setq epl ee)(c:llamarPL epl)(setq HNT WHNT)
          (redraw epl 3)
          (setq ee (handent HNT))
          (if (or (= ee nil)(= tieneP nil))
            (alert "   Acero sin Enlace   ")
            (if (= (entget ee) nil)
              (alert "   Acero sin Enlace   ")
              (setq etx ee)
            )
          )
        )
        (T (alert "   No se ha picado Texto Marca ni Acero   "))
      )
    )
  )

)

;---------
(DEFUN VERENLA ( / cont)
  (setq cont 0)       
  (setq s1 (ssget '((0 . "text,polyline") (-3 ("acerTX,acerPL")))))
  (if (= s1 nil)
    (alert "   No se ha seleccionado ni Marcas ni Aceros  ")
    (progn
      (setq ls1 (sslength s1))
      (setq contar 0)
      (repeat ls1
        (setq ne (ssname s1 contar))
        (setq propine (entget ne))
        (setq tipone (cdr (assoc 0 propine)))
        (if (= tipone "TEXT")
          (VERTEXT)
          (VERPOLYLINE)
        )
        (setq contar (1+ contar))
      )
    )
  )
  (if (= cont 0)
    (if (/= s1 nil)(alert "   Todos los Enlaces Correctos   "))
    (if (= cont 1)
      (alert (strcat "   " (itoa cont) " Enlace Incorrecto   "))
      (alert (strcat "   " (itoa cont) " Enlaces Incorrectos   "))
    )
  )
)

;---------
(DEFUN ENLA ()
  (c:llamarTX etx)
  (c:llamarPL epl)
  (if (or (= tieneV nil)(= tieneP nil))
    (alert "   No se puede Enlazar   ")
    (progn
      (redraw etx 3)(redraw epl 3)
      (setq codigo  Wcodigo) 
      (setq Mfija   WMfija) 
      (setq Mmarca  WMmarca) 
      (setq Mglobal WMglobal) 
      (setq Mtipo   WMTI) 
      (setq fi      Wfi) 
      (setq numero  Wnumero) 
      (setq HPL (cdr (assoc 5 (entget epl))))     
      (setq HTX     WHTX) 
      (setq HNT (cdr (assoc 5 (entget etx)))) 
      (setq reflejo Wreflejo)
      (setq posic   Wposic) 
      (setq fid  (itoa (- (length listfi)   (length (member fi listfi)))))
      (setq tipo (itoa (- (length listtipo) (length (member Mtipo listtipo)))))
      (setq aaa Wa11   bbb Wb11   ccc Wc11    ddd Wd11    eee We11    fff Wf11    ggg Wg11    rrr Wr11)
      (c:grabarTX etx)(c:grabarPL epl)
      (redraw etx 4)(redraw epl 4)
    )
  )
)

;---------
(DEFUN DESENLA ()
  (if (/= etx nil)
    (progn
      (redraw etx 3)
      (c:llamarTX etx)
      (if (/= tieneV nil)
        (progn
          (redraw etx 3)
          (setq codigo  Wcodigo) 
          (setq Mfija   WMfija) 
          (setq Mmarca  WMmarca) 
          (setq Mglobal WMglobal) 
          (setq Mtipo   WMtipo) 
          (setq fi      Wfi) 
          (setq numero  Wnumero) 
          (setq HPL "no")     
          (setq HTX     WHTX) 
          (setq reflejo Wreflejo)
          (setq posic   Wposic) 
          (setq fid  (itoa (- (length listfi)   (length (member fi listfi)))))
          (setq tipo (itoa (- (length listtipo) (length (member Mtipo listtipo)))))
          (setq aaa Wa11   bbb Wb11   ccc Wc11    ddd Wd11    eee We11    fff Wf11    ggg Wg11    rrr Wr11)
          (c:grabarTX etx)
          (redraw etx 4)
        )
      )
    )
  )
  (if (/= epl nil)
    (progn
      (redraw epl 3)
      (c:llamarPL epl)
      (if (/= tieneP nil)
        (progn
          (redraw epl 3)
          (setq Mtipo   WMTI) 
          (setq HNT "no") 
          (setq reflejo Wreflejo)
          (setq posic   Wposic) 
          (setq tipo (itoa (- (length listtipo) (length (member Mtipo listtipo)))))
          (setq aaa Wa11   bbb Wb11   ccc Wc11    ddd Wd11    eee We11    fff Wf11    ggg Wg11    rrr Wr11)
          (c:grabarPL epl)
          (redraw epl 4)
        )
      )
    )
  )

)

;---------
(DEFUN VERTEXT ()
  (c:llamarTX ne)
  (setq HPL WHPL)
  (setq enameHPL (handent HPL))
  (if (/= enameHPL nil)
    (if (/= (entget enameHPL) nil)
      (progn
        (c:llamarPL enameHPL)
        (setq HNT WHNT)
        (setq enameHNT (handent HNT))
        (if (not (eq ne enameHNT))
          (progn
            (redraw ne 3)
            (redraw enameHPL 3)
            (Walert "   Texto Marca con enlace Acero incorrecto   ")
            (setq cont (1+ cont))
            (redraw ne 4)
            (redraw enameHPL 4)
            (cond
              ((= opWa 1)
                (redraw ne 3)(setq ee ne)
                (SUPERENLACE)
                (if (= epl nil)
                   (alert "   Seleccion de Acero incorrecto   ")
                   (ENLA)
                )
                (if (/= etx nil)(redraw etx 3))
                (if (/= epl nil)(redraw epl 3))
                (if (= epl nil)
                  (getstring "\nEnlace no realizado...")
                  (getstring "\nEnlace realizado...")
                )
                (if (/= etx nil)(redraw etx 4))
                (if (/= epl nil)(redraw epl 4))
              )
              ((= opWa 2)
                (redraw ne 3)(setq ee ne)
                (DESENLACE)
                (DESENLA)
                (if (/= etx nil)(redraw etx 3))
                (if (/= epl nil)(redraw epl 3))
                (getstring "\nDesenlace realizado...")
                (if (/= etx nil)(redraw etx 4))
                (if (/= epl nil)(redraw epl 4))
              )
            )
          )
        )
      )
    )
  )
)

;---------
(DEFUN VERPOLYLINE ()
  (c:llamarPL ne)
  (setq HNT WHNT)
  (setq enameHNT (handent HNT))
  (if (/= enameHNT nil)
    (if (/= (entget enameHNT) nil)
      (progn
        (c:llamarTX enameHNT)
        (setq HPL WHPL)
        (setq enameHPL (handent HPL))
        (if (not (eq ne enameHPL))
          (progn
            (redraw ne 3)
            (redraw enameHNT 3)
            (Walert "   Acero con enlace Texto Marca incorrecto   ")
            (setq cont (1+ cont))
            (redraw ne 4)
            (redraw enameHNT 4)
            (cond
              ((= opWa 1)
                (redraw ne 3)(setq ee ne)
                (SUPERENLACE)
                (if (= etx nil)
                   (alert "   Seleccion de Texto Marca incorrecta   ")
                   (ENLA)
                )
                (if (/= etx nil)(redraw etx 3))
                (if (/= epl nil)(redraw epl 3))
                (if (= etx nil)
                  (getstring "\nEnlace no realizado...")
                  (getstring "\nEnlace realizado...")
                )
                (if (/= etx nil)(redraw etx 4))
                (if (/= epl nil)(redraw epl 4))
              )
              ((= opWa 2)
                (redraw ne 3)(setq ee ne)
                (DESENLACE)
                (DESENLA)
                (if (/= etx nil)(redraw etx 3))
                (if (/= epl nil)(redraw epl 3))
                (getstring "\nDesenlace realizado...")
                (if (/= etx nil)(redraw etx 4))
                (if (/= epl nil)(redraw epl 4))
              )
            )
          )
        )
      )
    )
  )
)

;---------
(DEFUN C:AGRUPAR ()
  (GRABAR_RESPALDO)
  (CARGAR "C:llamarTX" "datext")   
  (setvar "cmdecho" 0)
  (setvar "blipmode" 0)
  (setq opcionAGRUPAR 0)
  (SETQ DCL2 (LOAD_DIALOG "varios.dcl"))
  (SETQ CAJAB3 (NEW_DIALOG "agrupar" DCL2))
  
  (TIPOGRA2 "viga" "viga" "viga" 0)
  
  (if (= nom1ag nil)(setq nom1ag "V1"))
  (if (= alt1ag nil)(setq alt1ag "0.3"))

  (if (= agrup 1)(SET_TILE "agruparhierros"    "1"))
  (if (= agrup 2)(SET_TILE "veragrupamientos"  "1"))
  (if (= agrup 3)(SET_TILE "desagruparhierros" "1"))
  
  (set_tile "nom1" nom1ag)
  (set_tile "alt1" alt1ag)

  (action_tile "nom1" "(setq nom1ag (AR $value 5 -1 \"nom1\")  )")
  (action_tile "alt1" "(setq alt1ag (AR $value 5  2  \"alt1\")  )")
  (action_tile "nom2" "(setq opcionAGRUPAR 3)(done_dialog)")
  
  (action_tile "agruparhierros"    "(setq agrup 1)")
  (action_tile "veragrupamientos"  "(setq agrup 2)")
  (action_tile "desagruparhierros" "(setq agrup 3)")
  
  (action_tile "agrupar" "(setq opcionAGRUPAR 1)(done_dialog)")
  (action_tile "undover" "(setq opcionAGRUPAR 2)(done_dialog)")

  (START_DIALOG)
  (DONE_DIALOG)
  (UNLOAD_DIALOG DCL2)
  
  (cond
    ((= opcionAGRUPAR 3)
      (setvar "clayer" "0")
      (setq p1 (getpoint "\nPique Punto : "))
      (while (and p1 (/= nom1ag ""))
        (command "_text" "_j" "_m" p1 alt1ag 0 nom1ag)
        (setq p1 (getpoint "\nPique Punto : "))
      )
      (C:AGRUPAR)
    )
    ((= opcionAGRUPAR 2)
      (C:PANZOON1)
      (C:AGRUPAR)
    )
    ((and (= opcionAGRUPAR 1)(= agrup 1))
      (WNRAGRUPAR)
      (LLAMAR_RESPALDO)
      (C:AGRUPAR)
    )
    ((and (= opcionAGRUPAR 1)(= agrup 2))
      (setq et1 (entsel "\nSeleccione Texto o Polylinea : "))
      (while (/= et1 nil)
        (WNRMIRAR)
      )
      (LLAMAR_RESPALDO)
      (C:AGRUPAR)
    )
    ((and (= opcionAGRUPAR 1)(= agrup 3))
      (WNRDESAGRUPAR)
      (LLAMAR_RESPALDO)
      (C:AGRUPAR)
    )
  )

  (setvar "cmdecho" old2)
  (setvar "blipmode" blipmodeANT)
  (LLAMAR_RESPALDO)
)

;---------
(DEFUN WNRAGRUPAR ()
  (setq et1 (entsel "\nSeleccion Texto : "))
  (if (= et1 nil)
    (alert "   No se ha seleccionado nada   ")
    (progn
      (setq propiet1 (entget (car et1)))
      (setq tipoet1 (cdr (assoc 0 propiet1)))
      (if (/= tipoet1 "TEXT")
        (alert "   No se ha seleccionado Texto   ")
        (progn
          (redraw (car et1) 3)
          (setq HTX (cdr (assoc 5 propiet1)))
          (setq s1 (ssget '((0 . "text,polyline") (-3 ("acerTX,acerPL")))))
          (if (= s1 nil)
            (alert "   No se ha seleccionado ni Marcas ni Aceros  ")
            (progn
              (setq ls1 (sslength s1))
              (setq contar 0)
              (repeat ls1
                (setq ne (ssname s1 contar))
                (setq propine (entget ne))
                (setq tipone (cdr (assoc 0 propine)))
                (if (= tipone "TEXT")
                  (WNRTEXT)
                  (WNRPOLYLINE)
                )
                (setq contar (1+ contar))
              )
            )
          )
          (redraw (car et1) 4)
        )
      )
    )
  )

)

;---------
(DEFUN WNRMIRAR ()
  (if (= et1 nil)
    (alert "   No se ha seleccionado Nada   ")
    (progn
      (setq e (car et1))
      (setq propiet1 (entget e))
      (setq tipoet1 (cdr (assoc 0 propiet1)))
      (cond
        ((= tipoet1 "TEXT")
          (c:llamarTX e)
          (if (= tieneV nil)
            (progn
              (setq HTXpropio (cdr (assoc 5 propiet1))) 
              (setq textHTXv (cdr (assoc 1 propiet1)))
              (setq HTXv "no1" WHTX "no2" ya 0 HTX "no" selecace (ssadd))
                
              (setq s11p (ssget "x" '((0 . "text")(-3 ("acerTX")))))
              (if (/= s11p nil)
                (progn
                  (setq ls11p (sslength s11p))
                  (setq contarp 0)
                  (while (and (/= HTXpropio WHTX)(< contarp ls11p)(= ya 0))
                    (setq nep (ssname s11p contarp))
                    (c:llamarTX nep)
                    (if (/= WHTX "no")(setq selecace (ssadd nep selecace)))
                    (if (eq HTXpropio WHTX)
                      (setq HTX HTXpropio ya 1)
                    )
                    (setq contarp (1+ contarp))
                  )
                )
              )
              (setq s11v (ssget "x" (list (cons 1 textHTXv))))
              (setq ls11v (sslength s11v))
              (setq contarv 0)
              
              (setq HTXv "no1" WHTX "no2")
              (while (and (/= HTXv WHTX)(< contarv ls11v)(= ya 0))
                (setq nev (ssname s11v contarv))
                (setq HTXv (cdr (assoc 5 (entget nev)))) 
                
                (setq s11p selecace)
                (if (/= s11p nil)
                  (progn
                    (setq ls11p (sslength s11p))
                    (setq contarp 0)
                    (setq WHTX "no2")
                    (while (and (/= HTXv WHTX)(< contarp ls11p)(= ya 0))
                      (setq nep (ssname s11p contarp))
                      (c:llamarTX nep)
                      
                      (if (eq HTXv WHTX)
                        (setq HTX HTXv ya 1)
                      )
                      (setq contarp (1+ contarp))
                    )
                  )   
                )
                (setq contarv (1+ contarv))
              )
              (if (= HTX "no")(setq HTX HTXpropio))
              (SELECCIONAR)
            )
            (progn
              (setq HTX WHTX) 
              (SELECCIONAR)
            )
          )
        )
        ((= tipoet1 "POLYLINE")
          (c:llamarPL e)
          (if (= WHNT "no")
            (progn
              (alert "   No existe agrupamiento   ")
              (setq et1 (entsel "\nSeleccione Texto o Polylinea : "))
            )
            (progn
              (setq ee (handent WHNT))
              (if (= ee nil)
                (progn
                  (alert "   No existe agrupamiento   ")
                  (setq et1 (entsel "\nSeleccione Texto o Polylinea : "))
                )
                (if (= (entget ee) nil)
                  (progn
                    (alert "   No existe agrupamiento   ")
                    (setq et1 (entsel "\nSeleccione Texto o Polylinea : "))
                  )
                  (progn
                    (c:llamarTX ee)
                    (setq HTX WHTX) 
                    (SELECCIONAR)
                  )
                )
              )
            )
          )
        )
        (T 
          (alert "   No se ha seleccionado Texto ni Polylinea   ")
          (setq et1 (entsel "\nSeleccione Texto o Polylinea : "))
        )
      )
    )
  )

)

;---------
(DEFUN WNRDESAGRUPAR ()
  (setq HTX "no")
  (setq s1 (ssget '((0 . "text,polyline") (-3 ("acerTX,acerPL")))))
  (if (= s1 nil)
    (alert "   No se ha seleccionado ni Marcas ni Aceros  ")
    (progn
      (setq ls1 (sslength s1))
      (setq contar 0)
      (repeat ls1
        (setq ne (ssname s1 contar))
        (setq propine (entget ne))
        (setq tipone (cdr (assoc 0 propine)))
        (if (= tipone "TEXT")
          (WNRTEXT)
          (WNRPOLYLINE)
        )
        (setq contar (1+ contar))
      )
    )
  )

)

;---------
(DEFUN SELECCIONAR ()
  (if (= HTX "no")
    (progn
      (alert "   No existe agrupamiento   ")
      (setq et1 (entsel "\nSeleccione Texto o Polylinea : "))
    )
    (progn
      (setq enameHTX (handent HTX))
      (if (= enameHTX nil)
        (progn
          (alert "   No existe agrupamiento   ")
          (setq et1 (entsel "\nSeleccione Texto o Polylinea : "))
        )
        (if (= (entget enameHTX) nil)
          (progn
            (alert "   No existe agrupamiento   ")
            (setq et1 (entsel "\nSeleccione Texto o Polylinea : "))
          )
          (progn
            (setq textHTX (cdr (assoc 1 (entget enameHTX))))
            (TEXTOS1 3)(ACEROS1 3)
            (print "Seleccion Completa")
            (setq et1 (entsel "\nSeleccione Texto o Polylinea : "))
            (TEXTOS1 4)(ACEROS1 4)
          )
        )
      )
    )
  )

)

;---------
(DEFUN TEXTOS1 (resaltado)
  (setq s11 (ssget "x" (list (cons 1 textHTX))))
  (if (/= s11 nil)
    (progn
      (setq ls11 (sslength s11))
      (setq contar 0)
      (repeat ls11
        (setq ne (ssname s11 contar))
        (redraw ne resaltado)
        (setq contar (1+ contar))
      )
    )
  )

)

;---------
(DEFUN ACEROS1 (resaltado)
  (setq s11 (ssget "x" '((0 . "text")(-3 ("acerTX")))))
  (if (/= s11 nil)
    (progn
      (setq ls11 (sslength s11))
      (setq contar 0)
      (repeat ls11
        (setq ne (ssname s11 contar))
        (c:llamarTX ne)
        (if (= HTX WHTX)
          (progn
            (redraw ne resaltado)
            (setq ew (handent WHPL))
            (if (/= ew nil)
              (if (/= (entget ew) nil)
                (redraw ew resaltado)
              )
            )
          )
        )
        (setq contar (1+ contar))
      )
    )
  )


)

;---------
(DEFUN WNRTEXT ()
  (redraw ne 3)
  (c:llamarTX ne)
  
  (setq codigo  Wcodigo) 
  (setq Mfija   WMfija) 
  (setq Mmarca  WMmarca) 
  (setq Mglobal WMglobal) 
  (setq Mtipo   WMtipo) 
  (setq fi      Wfi) 
  (setq numero  Wnumero) 
  (setq HPL     WHPL) 
  ;(setq HTX     WHTX) 
  (setq reflejo Wreflejo)
  (setq posic   Wposic) 
  (setq fid  (itoa (- (length listfi)   (length (member fi listfi)))))
  (setq tipo (itoa (- (length listtipo) (length (member Mtipo listtipo)))))
  (setq aaa Wa11   bbb Wb11   ccc Wc11    ddd Wd11    eee We11    fff Wf11    ggg Wg11    rrr Wr11)
  (c:grabarTX ne)
  (redraw ne 4)
)

;---------
(DEFUN WNRPOLYLINE ()
  (redraw ne 3)
  (c:llamarPL ne)
  (redraw ne 4)
  
  (setq ne (handent WHNT))
  (if (/= ne nil)
    (if (/= (entget ne))
      (WNRTEXT)
    )
  )
)

;---------
(DEFUN C:BORRARMARCAS ()
  (setvar "cmdecho" 0)
  (setq opcionBORRAR 0)
  (SETQ DCL2 (LOAD_DIALOG "varios.dcl"))
  (SETQ CAJAB3 (NEW_DIALOG "borrar" DCL2))
  
  (if (= borrado  nil) (SETQ borrado   3))
  
  (if (= borrado 1)(SET_TILE "bmarcas"        "1"))
  (if (= borrado 2)(SET_TILE "baceros"        "1"))
  (if (= borrado 3)(SET_TILE "bmarcasyaceros" "1"))
  
  (action_tile "bmarcas"        "(setq borrado 1)")
  (action_tile "baceros"        "(setq borrado 2)")
  (action_tile "bmarcasyaceros" "(setq borrado 3)")
  
  (action_tile "bborrar" "(setq opcionBORRAR 1)(done_dialog)")

  (START_DIALOG)
  (DONE_DIALOG)
  (UNLOAD_DIALOG DCL2)
  
  (cond
    ((and (= opcionBORRAR 1)(= borrado 1))
      (setq s1 (ssget '((0 . "text") (-3 ("acerTX")))))
      (if (= s1 nil)
        (alert "   No se ha seleccionado Ninguna Marca   ")
        
        (command "_erase" s1 "")
      
      )
    )
    ((and (= opcionBORRAR 1)(= borrado 2))
      (setq s1 (ssget '((0 . "polyline") (-3 ("acerPL")))))
      (if (= s1 nil)
        (alert "   No se ha seleccionado Ningun Acero   ")
        (command "_erase" s1 "")
      )
    )
    ((and (= opcionBORRAR 1)(= borrado 3))
      (setq s1 (ssget '((0 . "text,polyline") (-3 ("acerTX,acerPL")))))
      (if (= s1 nil)
        (alert "   No se ha seleccionado ni Marca ni Acero  ")
        (command "_erase" s1 "")
      )
    )
  )

  (setvar "cmdecho" old2)

)

;---------
(DEFUN C:CAMBIARTEXT (opcambiar)
  (CARGAR "C:llamarTX" "datext")   
  (setvar "cmdecho" 0)
  (if (= opcambiar 0)(setq s1 (ssget '((0 . "text") (-3 ("acerTX"))))))
  (if (= opcambiar 1)(setq s1 (ssget "x" '((0 . "text") (-3 ("acerTX"))))))
  (if (= opcambiar 2)(setq s1 selen))
    
  (if (= s1 nil)
    (alert "   No se ha seleccionado Ninguna Marca   ")
    (progn
      (setq ls1 (sslength s1))
      (setq contar 0)
      (repeat ls1
        (setq enttt (ssname s1 contar))
        (c:llamarTX enttt)
        (setq Wfid  (itoa (- (length listfi)   (length (member Wfi listfi)))))
        (if (= Wcodigo "0")
          (setq Wcero 0)
          (setq Wcero 1)
        )
        (setq tt (TEXTOMARCA Wcodigo Wcero WMfija WMmarca WMglobal oppremar Wfid Wnumero WMtipo))
        (command "_change" enttt "" "" "" stylomarca "" "" tt)
        (setq contar (1+ contar))
      )
    )
  )
  (setvar "cmdecho" old2)
  (setvar "TEXTSTYLE" stitextANT)
)

;---------
(DEFUN C:MARCASYACEROS ()
  (setvar "cmdecho" 0)
  (command "_layer" "_m" layermar "")
  (command "_layer" "_m" layerace "")
  
  (setq s1 (ssget '((0 . "text,polyline") (-3 ("acerTX,acerPL")))))
  (if (= s1 nil)
    (alert "   No se ha seleccionado Ninguna Marca ni Acero   ")
    (progn
      (setq ls1 (sslength s1))
      (setq contar 0)
      (repeat ls1
        (setq enttt (ssname s1 contar))
        (setq propienttt (entget enttt))
        (setq tipoenttt (cdr (assoc 0 propienttt)))
        (cond
          ((= tipoenttt "TEXT")
            (command "_change" enttt "" "" "" stylomarca altmar "" "")
            (command "_change" enttt "" "_p" "_la" layermar "")
          )
          ((= tipoenttt "POLYLINE")
            (command "_pedit" enttt "_w" espace "")
            (command "_change" enttt "" "_p" "_la" layerace "")
          )
        )
        (setq contar (1+ contar))
      )
    )
  )
  (setvar "cmdecho" old2)
  (setvar "TEXTSTYLE" stitextANT)
)
;---------
(DEFUN C:MARCAS ()
  (setvar "cmdecho" 0)
  (command "_layer" "_m" layermar "")
  (setq s1 (ssget '((0 . "text") (-3 ("acerTX")))))
  (if (= s1 nil)
    (alert "   No se ha seleccionado Ninguna Marca   ")
    (progn
      (setq ls1 (sslength s1))
      (setq contar 0)
      (repeat ls1
        (setq enttt (ssname s1 contar))
        (command "_change" enttt "" "" "" stylomarca altmar "" "")
        (command "_change" enttt "" "_p" "_la" layermar "")
        (setq contar (1+ contar))
      )
    )
  )
  (setvar "cmdecho" old2)
  (setvar "TEXTSTYLE" stitextANT)
)

;---------
(DEFUN C:ACEROS ()
  (setvar "cmdecho" 0)
  (command "_layer" "_m" layerace "")
  (setq s1 (ssget '((0 . "polyline") (-3 ("acerPL")))))
  (if (= s1 nil)
    (alert "   No se ha seleccionado Ningun Acero   ")
    (progn
      (setq ls1 (sslength s1))
      (setq contar 0)
      (repeat ls1
        (setq enttt (ssname s1 contar))
        (command "_pedit" enttt "_w" espace "")
        (command "_change" enttt "" "_p" "_la" layerace "")
        (setq contar (1+ contar))
      )
    )
  )
  (setvar "cmdecho" old2)
)
;---------
(DEFUN GRABAR_RESPALDO ()
  (setq Rcodigo  codigo) 
  (setq RMfija   Mfija) 
  (setq RMmarca  Mmarca) 
  (setq RMglobal Mglobal) 
  (setq RMtipo   Mtipo) 
  (setq Rfi      fi) 
  (setq Rtipo    tipo) 
  (setq Rfid     fid) 
  (setq Rnumero  numero) 
  (setq Raaa     aaa) 
  (setq Rbbb     bbb) 
  (setq Rccc     ccc) 
  (setq Rddd     ddd) 
  (setq Reee     eee) 
  (setq Rfff     fff) 
  (setq Rggg     ggg) 
  (setq Rrrr     rrr) 
  (setq Rreflejo reflejo) 
  (setq Rposic   posic) 
)

;---------
(DEFUN LLAMAR_RESPALDO ()
  (setq codigo  Rcodigo) 
  (setq Mfija   RMfija) 
  (setq Mmarca  RMmarca) 
  (setq Mglobal RMglobal) 
  (setq Mtipo   RMtipo) 
  (setq fi      Rfi) 
  (setq tipo    Rtipo) 
  (setq fid     Rfid) 
  (setq numero  Rnumero) 
  (setq aaa     Raaa) 
  (setq bbb     Rbbb) 
  (setq ccc     Rccc) 
  (setq ddd     Rddd) 
  (setq eee     Reee) 
  (setq fff     Rfff) 
  (setq ggg     Rggg) 
  (setq rrr     Rrrr) 
  (setq reflejo Rreflejo) 
  (setq posic   Rposic) 
)
;---------
(DEFUN LLAMAR_RESPALDO_ACT ()
  (if (= actmarca  "1")(setq Mmarca  RMmarca))
  
  (if (= actmarca  "0")
    (setq Mmarca (itoa (+ (atoi incmar) (atoi Mmarca))))
  )

  (if (= actglobal "1")(setq Mglobal RMglobal)) 
  (if (= actfija   "1")(setq Mfija   MMfija)) 
  (if (= actcero   "1")(setq cero    Rcero))
  
  (if (= acttipo   "1")(setq Mtipo   RMtipo)) 
  (if (= acttipo   "1")(setq tipo    Rtipo)) 
  (if (= actfi     "1")(setq fi      Rfi)) 
  (if (= actfi     "1")(setq fid     Rfid)) 
  (if (= actnumero "1")(setq numero  Rnumero)) 
  
  (if (= actangulo  "1")(setq angulo  Rangulo)) 
  (if (= actposic   "1")(setq posic   Rposic)) 
  (if (= actreflejo "1")(setq reflejo Rreflejo)) 
  
  (if (= acta "1")(setq aaa  Raaa)) 
  (if (= actb "1")(setq bbb  Rbbb)) 
  (if (= actc "1")(setq ccc  Rccc)) 
  (if (= actd "1")(setq ddd  Rddd)) 
  (if (= acte "1")(setq eee  Reee)) 
  (if (= actf "1")(setq fff  Rfff)) 
  (if (= actg "1")(setq ggg  Rggg)) 
  (if (= actr "1")(setq rrr  Rrrr)) 
)
;---------
(DEFUN EARREGLO ()
  (SET_TILE "verenla"   "0")
  (SET_TILE "enla"      "0")
  (SET_TILE "desenla"   "0")
  (SET_TILE "mirarenla" "0")
  
  (if (= enlac 1)(SET_TILE "verenla"   "1"))
  (if (= enlac 2)(SET_TILE "enla"      "1"))
  (if (= enlac 3)(SET_TILE "desenla"   "1"))
  (if (= enlac 4)(SET_TILE "mirarenla" "1"))

)

;---------
(DEFUN DARREGLO ()
  (SET_TILE "Dbloques"  "0")
  (SET_TILE "Dmarcas"   "0")
  (SET_TILE "Dvigas"    "0")
  (SET_TILE "Destribos" "0")
  (SET_TILE "Dgradas"   "0")
  (SET_TILE "Dvarios"   "0")
  (SET_TILE "Dlosa"     "0")
  (SET_TILE "Dcorte"    "0")
  
  (if (= dibuj 1)(SET_TILE "Dbloques"  "1"))
  (if (= dibuj 2)(SET_TILE "Dmarcas"   "1"))
  (if (= dibuj 3)(SET_TILE "Dvigas"    "1"))
  (if (= dibuj 4)(SET_TILE "Destribos" "1"))
  (if (= dibuj 5)(SET_TILE "Dgradas"   "1"))
  (if (= dibuj 6)(SET_TILE "Dvarios"   "1"))
  (if (= dibuj 7)(SET_TILE "Dlosa"     "1"))
  (if (= dibuj 8)(SET_TILE "Dcorte"    "1"))
)

;---------
(DEFUN Walert (Wtexto)
  (setq opWa 0)
  (SETQ DCL2 (LOAD_DIALOG "varios.dcl"))
  (SETQ CAJAB5 (NEW_DIALOG "Walert" DCL2))
  
  
  (SET_TILE "Wtexto" Wtexto)
  
  (action_tile "Wenla"    "(setq opWa 1)(done_dialog)")
  (action_tile "Wdesenla" "(setq opWa 2)(done_dialog)")

  (START_DIALOG)
  (DONE_DIALOG)
  (UNLOAD_DIALOG DCL2)

)

;----------
(DEFUN GRATEXT_ACT ()      
     (if (= actcero "0")(setq cero 1))
     (TEXTO lista1 tipo angulo)
)     
;----------
(DEFUN GRAPOLY_ACT ()      
     (DIBUJO punto tipo layerace espace (atof aaa) (atof bbb) (atof ccc) (atof ggg) (atof rrr)) 
     (REFLEJE ent punto reflejo)
     (MOVERROTAR ent (atof aaa) posic punto angulo)
)     

;----------
(DEFUN OBTANGULOPOLY ()      
  (setq lista1 (ARMAR eeppll))
  (cond
    ((or (= tipo "0") (and (or (= tipo "1")(= tipo "3")(= tipo "4"))(< (atof ggg) 0.001)))
      (setq p1 (nth 0 lista1) p2 (nth 1 lista1))
    )
    ((and (= tipo "1")(> (atof ggg) 0.001))
      (setq p1 (nth 2 lista1) p2 (nth 3 lista1))
    )
    ((= tipo "2")
      (setq p1 (nth 1 lista1) p2 (nth 2 lista1))
    )
    ((and (= tipo "3")(> (atof ggg) 0.001))
      (setq p1 (nth 2 lista1) p2 (nth 3 lista1))
    )
    ((and (= tipo "4")(> (atof ggg) 0.001))
      (setq p1 (nth 2 lista1) p2 (nth 3 lista1))
    )
    ((= tipo "5")
      (setq p1 (nth 1 lista1) p2 (nth 2 lista1))
    )
  )
  (if (or (= reflejo 1)(= reflejo 4))
    (setq angulo (rtos (/ (* (angle p1 p2) 180) pi) 2 0))
    (setq angulo (rtos (/ (* (angle p2 p1) 180) pi) 2 0))
  )
)         
;----------
(DEFUN OBTANGULOTEXT ()      
  (setq angulo (rtos (/ (* (cdr (assoc 50 (entget eettxx))) 180) pi) 2 0))
)
;----------
(DEFUN C:NUMCODMAX ()      
  (setq ncm 0)
  (GRABAR_RESPALDO)
  (setq s1 (ssget "x" '((0 . "text") (-3 ("acerTX")))))
  (if (= s1 nil)
    (alert "   No Existen Aceros  ")
    (progn
      (setq ls1 (sslength s1))
      (setq contar 0)
      (repeat ls1
        (setq e1 (ssname s1 contar))
        (c:llamarTX e1)
        (if (>= (atoi Wcodigo) ncm)(setq ncm (atoi Wcodigo)))
        (setq contar (1+ contar))
      )
    )
  )
  (setvar "useri1" (1+ ncm))
  (setq ncm (itoa ncm))
  (LLAMAR_RESPALDO)
  (print (strcat "Numero Codigos : " ncm))
  nil
)
;----------
(DEFUN C:NUMERARCOD ()      
  (setq ncm 0)
  (GRABAR_RESPALDO)
  (setq s1 (ssget "x" '((0 . "text") (-3 ("acerTX")))))
  (if (= s1 nil)
    (alert "   No Existen Aceros  ")
    (progn
      (setq ls1 (sslength s1))
      (setq contar 0)
      (repeat ls1
        (setq e1 (ssname s1 contar))
        (c:llamarTX e1)
        (if (/= Wcodigo "0")
          (progn
            (setq Mfija   WMfija) 
            (setq Mmarca  WMmarca) 
            (setq Mglobal WMglobal) 
            (setq Mtipo   WMtipo) 
            (setq fi      Wfi) 
            (setq numero  Wnumero) 
            (setq reflejo Wreflejo)
            (setq posic   Wposic) 
            (setq fid  (itoa (- (length listfi)   (length (member fi listfi)))))
            (setq tipo (itoa (- (length listtipo) (length (member Mtipo listtipo)))))
            (setq aaa Wa11   bbb Wb11   ccc Wc11    ddd Wd11    eee We11    fff Wf11    ggg Wg11   rrr Wr11)
            (setq HPL   WHPL) 
            (setq HTX   WHTX) 
     
            (setq ncm (1+ ncm))(setq codigo (itoa ncm))
            (c:grabarTX e1)
          )
        )
        (setq contar (1+ contar))
      )
    )
  )
  (setvar "useri1" (1+ ncm))
  (setq ncm (itoa ncm))
  (LLAMAR_RESPALDO)
  (print (strcat "Numero Codigos : " ncm))
  (C:CAMBIARTEXT 1)
  nil
)
;----------
(DEFUN C:DATGRA ()      
  (GRABAR_RESPALDO)
  (ACTUAL 1)
  (LLAMAR_RESPALDO)
  nil
)
;----------
(defun C:PPLL (ee / old3)
  (setq old3 (getvar "cmdecho"))
  (setvar "cmdecho" 0)
  (setq lista11 (ARMAR ee))
  
  (setq Wa11 "0.00" Wb11 "0.00" Wc11 "0.00" Wd11 "0.00" We11 "0.00" Wf11 "0.00" Wr11 "0.00")
  
  (cond
    ((= WMTI "I1")
      (setq Wa11 (distance (nth 0 lista11) (nth 1 lista11)))
      (setq Wa11 (rtos Wa11 2 2))
    )
    ((and (= WMTI "I") (= (length lista11) 6))
      (setq Wr11 (/ (distance (nth 1 lista11) (nth 2 lista11)) 2.0))
      (setq Wa11 (+ (* Wr11 2) (distance (nth 2 lista11) (nth 3 lista11))))
      (setq Wg11 (+ Wr11 (distance (nth 0 lista11) (nth 1 lista11))))
      (setq Wr11 (rtos Wr11 2 2))
      (setq Wa11 (rtos Wa11 2 2))
      (setq Wg11 (rtos Wg11 2 2))
    )
    ((and (= WMTI "I") (= (length lista11) 2))
      (setq Wa11 (distance (nth 0 lista11) (nth 1 lista11)))
      (setq Wa11 (rtos Wa11 2 2))
    )
    ((= WMTI "C")
      (setq Wa11 (distance (nth 1 lista11) (nth 2 lista11)))
      (setq Wb11 (distance (nth 0 lista11) (nth 1 lista11)))
      (setq Wa11 (rtos Wa11 2 2))
      (setq Wb11 (rtos Wb11 2 2))
    )
    ((and (= WMTI "O") (= (length lista11) 12))
      (setq Wr11 (/ (distance (nth 3 lista11) (nth 4 lista11)) 1.414213562))
      (setq Wa11 (+ (* Wr11 2) (distance (nth 2 lista11) (nth 3 lista11))))
      (setq Wb11 (+ (* Wr11 2) (distance (nth 4 lista11) (nth 5 lista11))))
      (setq Wg11 (+ Wr11 (distance (nth 0 lista11) (nth 1 lista11))))
      (setq Wr11 (rtos Wr11 2 2))
      (setq Wa11 (rtos Wa11 2 2))
      (setq Wb11 (rtos Wb11 2 2))
      (setq Wg11 (rtos Wg11 2 2))
    )
    ((and (= WMTI "O") (= (length lista11) 8))
      (setq Wr11 (/ (distance (nth 1 lista11) (nth 2 lista11)) 1.414213562))
      (setq Wa11 (+ (* Wr11 2) (distance (nth 0 lista11) (nth 1 lista11))))
      (setq Wb11 (+ (* Wr11 2) (distance (nth 2 lista11) (nth 3 lista11))))
      (setq Wr11 (rtos Wr11 2 2))
      (setq Wa11 (rtos Wa11 2 2))
      (setq Wb11 (rtos Wb11 2 2))
    )
    ((and (= WMTI "L") (= (length lista11) 5))
      (setq Wr11 (/ (distance (nth 1 lista11) (nth 2 lista11)) 2.0))
      (setq Wa11 (+ (* Wr11 2) (distance (nth 2 lista11) (nth 3 lista11))))
      (setq Wb11 (distance (nth 3 lista11) (nth 4 lista11)))
      (setq Wg11 (+ Wr11 (distance (nth 0 lista11) (nth 1 lista11))))
      (command "_ucs" "_e" ee)
      (setq p4 (trans (nth 3 lista11) 0 1)) 
      (setq p5 (trans (nth 4 lista11) 0 1)) 
      (command "_ucs" "_w")
      (setq pdd (nth 1 (mapcar '- p5 p4)))
      (if (> pdd 0)(setq Wb11 (* Wb11 -1.0)))
      (setq Wr11 (rtos Wr11 2 2))
      (setq Wa11 (rtos Wa11 2 2))
      (setq Wb11 (rtos Wb11 2 2))
      (setq Wg11 (rtos Wg11 2 2))
    )
    ((and (= WMTI "L") (= (length lista11) 3))
      (setq Wa11 (distance (nth 0 lista11) (nth 1 lista11)))
      (setq Wb11 (distance (nth 1 lista11) (nth 2 lista11)))
      (command "_ucs" "_e" ee)
      (setq p2 (trans (nth 1 lista11) 0 1)) 
      (setq p3 (trans (nth 2 lista11) 0 1)) 
      (command "_ucs" "_w")
      (setq pdd (nth 1 (mapcar '- p3 p2)))
      (if (< pdd 0)(setq Wb11 (* Wb11 -1.0)))
      (setq Wa11 (rtos Wa11 2 2))
      (setq Wb11 (rtos Wb11 2 2))
    )
    ((= WMTI "G") 
      (setq Wa11 (distance (nth 1 lista11) (nth 2 lista11)))
      (setq Wb11 (distance (nth 0 lista11) (nth 1 lista11)))
      (setq Wc11 (distance (nth 2 lista11) (nth 3 lista11)))
      (command "_ucs" "_3" (nth 1 lista11) (nth 2 lista11)  (polar (nth 1 lista11) (+ (gra 90) (angle (nth 1 lista11) (nth 2 lista11))) 1))
      (setq p1 (trans (nth 0 lista11) 0 1)) 
      (setq p2 (trans (nth 1 lista11) 0 1)) 
      (setq p3 (trans (nth 2 lista11) 0 1)) 
      (setq p4 (trans (nth 3 lista11) 0 1)) 
      (command "_ucs" "_w")
      (setq pd1 (nth 1 (mapcar '- p1 p2)))
      (setq pd2 (nth 1 (mapcar '- p4 p3)))
      (if (> pd1 0)(setq Wb11 (* Wb11 -1.0)))
      (if (> pd2 0)(setq Wc11 (* Wc11 -1.0)))
      (setq Wa11 (rtos Wa11 2 2))
      (setq Wb11 (rtos Wb11 2 2))
      (setq Wc11 (rtos Wc11 2 2))
    )
  )
  (setvar "cmdecho" old3)
)
