(DEFUN C:LEER ()
  (SETQ ARCHI (OPEN "C:/SOPORTE/BLOQUE1.TXT" "R"))
  (SETQ ARCHIW (OPEN "C:/SOPORTE/BLOQUE2.TXT" "W"))
  (WHILE (SETQ LEARCHI (READ-LINE ARCHI))
    (WRITE-LINE LEARCHI ARCHIW)
    (PRINT LEARCHI)
  )
  (CLOSE ARCHIW)
  (CLOSE ARCHI)
)
